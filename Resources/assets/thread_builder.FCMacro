import FreeCAD
import math
import DraftGeomUtils
import Draft

#used to build the internal_data and external_data values
#need to sketch the profiles, common with the line at z=0 though z=1
#set a breakpoint in vs2017 to view the text representation of t_str

#parameters
#pitch = 1.0
#height = 10.0
#major_diameter = 6
minor_diameter = 10
#external = True

#h = pitch * 0.866025
#r = pitch * 1.4434
mk_bsplines = False
if mk_bsplines:
    int_pts = []
    ext_pts = []


sel = Gui.Selection.getSelectionEx()
if len(sel)!=3:
   FreeCAD.Console.PrintMessage("select 3 shapes: 1 = line object, 2 = internal sketch, 3 external sketch\n")
   raise Exception("Select 3 shapes\n")
line_obj = sel[0].Object
int_sketch = sel[1].Object
ext_sketch = sel[2].Object
pitch = int_sketch.getDatum("pitch").Value

def getIntersection(z, sk,):
    if mk_bsplines:
        global int_pts, ext_pts

    line_obj.Placement = App.Placement(App.Vector(0,0,z), App.Rotation(App.Vector(0,0,1),0), App.Vector(0,0,0))
    common = line_obj.Shape.cut(sk.Shape)
    if mk_bsplines:
        if "ext_45" == sk.Label:
            ext_pts += [common.Vertex2.Point]
        else:
            int_pts += [common.Vertex2.Point]
    return common.Vertex2.Point.x




int_intersections = []
ext_intersections = []
resolution = int(720) # 2 points per degree

for rr in range(1,resolution):
    int_intersections.append(round(getIntersection(float(rr*pitch)/float(resolution),int_sketch)-minor_diameter/2.0,12))
    ext_intersections.append(round(getIntersection(float(rr*pitch)/float(resolution),ext_sketch)-minor_diameter/2.0,12))
t_i = tuple(int_intersections)
t_e = tuple(ext_intersections)
t_str_ext = "external_data = ["
t_str_int = "internal_data = ["

for ii in t_i:
    t_str_int+=str(ii)+","
t_str_int+="]"

for ee in t_e:
    t_str_ext+=str(ee)+","
t_str_ext+="]"

if mk_bsplines:
    Draft.makeBSpline(int_pts)
    Draft.makeBSpline(ext_pts)
#FreeCAD.Console.PrintMessage(t_str)
pass
#from vs 2019 after copying t_str_??t
#internal45_data = [-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,0.001388888889,0.002777777778,0.004166666667,0.005555555556,0.006944444444,0.008333333333,0.009722222222,0.011111111111,0.0125,0.013888888889,0.015277777778,0.016666666667,0.018055555556,0.019444444444,0.020833333333,0.022222222222,0.023611111111,0.025,0.026388888889,0.027777777778,0.029166666667,0.030555555556,0.031944444444,0.033333333333,0.034722222222,0.036111111111,0.0375,0.038888888889,0.040277777778,0.041666666667,0.043055555556,0.044444444444,0.045833333333,0.047222222222,0.048611111111,0.05,0.051388888889,0.052777777778,0.054166666667,0.055555555556,0.056944444444,0.058333333333,0.059722222222,0.061111111111,0.0625,0.063888888889,0.065277777778,0.066666666667,0.068055555556,0.069444444444,0.070833333333,0.072222222222,0.073611111111,0.075,0.076388888889,0.077777777778,0.079166666667,0.080555555556,0.081944444444,0.083333333333,0.084722222222,0.086111111111,0.0875,0.088888888889,0.090277777778,0.091666666667,0.093055555556,0.094444444444,0.095833333333,0.097222222222,0.098611111111,0.1,0.101388888889,0.102777777778,0.104166666667,0.105555555556,0.106944444444,0.108333333333,0.109722222222,0.111111111111,0.1125,0.113888888889,0.115277777778,0.116666666667,0.118055555556,0.119444444444,0.120833333333,0.122222222222,0.123611111111,0.125,0.126388888889,0.127777777778,0.129166666667,0.130555555556,0.131944444444,0.133333333333,0.134722222222,0.136111111111,0.1375,0.138888888889,0.140277777778,0.141666666667,0.143055555556,0.144444444444,0.145833333333,0.147222222222,0.148611111111,0.15,0.151388888889,0.152777777778,0.154166666667,0.155555555556,0.156944444444,0.158333333333,0.159722222222,0.161111111111,0.1625,0.163888888889,0.165277777778,0.166666666667,0.168055555556,0.169444444444,0.170833333333,0.172222222222,0.173611111111,0.175,0.176388888889,0.177777777778,0.179166666667,0.180555555556,0.181944444444,0.183333333333,0.184722222222,0.186111111111,0.1875,0.188888888889,0.190277777778,0.191666666667,0.193055555556,0.194444444444,0.195833333333,0.197222222222,0.198611111111,0.2,0.201388888889,0.202777777778,0.204166666667,0.205555555556,0.206944444444,0.208333333333,0.209722222222,0.211111111111,0.2125,0.213888888889,0.215277777778,0.216666666667,0.218055555556,0.219444444444,0.220833333333,0.222222222222,0.223611111111,0.225,0.226388888889,0.227777777778,0.229166666667,0.230555555556,0.231944444444,0.233333333333,0.234722222222,0.236111111111,0.2375,0.238888888889,0.240277777778,0.241666666667,0.243055555556,0.244444444444,0.245833333333,0.247222222222,0.248611111111,0.25,0.251388888889,0.252777777778,0.254166666667,0.255555555556,0.256944444444,0.258333333333,0.259722222222,0.261111111111,0.2625,0.263888888889,0.265277777778,0.266666666667,0.268055555556,0.269444444444,0.270833333333,0.272222222222,0.273611111111,0.275,0.276388888889,0.277777777778,0.279166666667,0.280555555556,0.281944444444,0.283333333333,0.284722222222,0.286111111111,0.2875,0.288888888889,0.290277777778,0.291666666667,0.293055555556,0.294444444444,0.295833333333,0.297222222222,0.298611111111,0.3,0.301388888889,0.302777777778,0.304166666667,0.305555555556,0.306944444444,0.308333333333,0.309722222222,0.311111111111,0.3125,0.313858688514,0.315159467254,0.316405739377,0.317600519576,0.318746492615,0.319846060893,0.320901383434,0.321914408144,0.322886898686,0.323820457033,0.324716542535,0.325576488113,0.326401514108,0.327192740176,0.327951195558,0.32867782799,0.329373511457,0.330039052968,0.330675198508,0.331282638269,0.331862011268,0.33241390944,0.33293888126,0.333437434977,0.333910041483,0.334357136884,0.334779124789,0.335176378369,0.335549242191,0.335898033867,0.336223045529,0.336524545151,0.336802777733,0.337057966357,0.337290313125,0.3375,0.337687189543,0.33785202556,0.337994633675,0.338115121809,0.338213580601,0.338290083752,0.338344688299,0.338377434833,0.338388347648,0.338377434833,0.338344688299,0.338290083752,0.338213580601,0.338115121809,0.337994633675,0.33785202556,0.337687189543,0.3375,0.337290313125,0.337057966357,0.336802777733,0.336524545151,0.336223045529,0.335898033867,0.335549242191,0.335176378369,0.334779124789,0.334357136884,0.333910041483,0.333437434977,0.33293888126,0.33241390944,0.331862011268,0.331282638269,0.330675198508,0.330039052968,0.329373511457,0.32867782799,0.327951195558,0.327192740176,0.326401514108,0.325576488113,0.324716542535,0.323820457033,0.322886898686,0.321914408144,0.320901383434,0.319846060893,0.318746492615,0.317600519576,0.316405739377,0.315159467254,0.313858688514,0.3125,0.311111111111,0.309722222222,0.308333333333,0.306944444444,0.305555555556,0.304166666667,0.302777777778,0.301388888889,0.3,0.298611111111,0.297222222222,0.295833333333,0.294444444444,0.293055555556,0.291666666667,0.290277777778,0.288888888889,0.2875,0.286111111111,0.284722222222,0.283333333333,0.281944444444,0.280555555556,0.279166666667,0.277777777778,0.276388888889,0.275,0.273611111111,0.272222222222,0.270833333333,0.269444444444,0.268055555556,0.266666666667,0.265277777778,0.263888888889,0.2625,0.261111111111,0.259722222222,0.258333333333,0.256944444444,0.255555555556,0.254166666667,0.252777777778,0.251388888889,0.25,0.248611111111,0.247222222222,0.245833333333,0.244444444444,0.243055555556,0.241666666667,0.240277777778,0.238888888889,0.2375,0.236111111111,0.234722222222,0.233333333333,0.231944444444,0.230555555556,0.229166666667,0.227777777778,0.226388888889,0.225,0.223611111111,0.222222222222,0.220833333333,0.219444444444,0.218055555556,0.216666666667,0.215277777778,0.213888888889,0.2125,0.211111111111,0.209722222222,0.208333333333,0.206944444444,0.205555555556,0.204166666667,0.202777777778,0.201388888889,0.2,0.198611111111,0.197222222222,0.195833333333,0.194444444444,0.193055555556,0.191666666667,0.190277777778,0.188888888889,0.1875,0.186111111111,0.184722222222,0.183333333333,0.181944444444,0.180555555556,0.179166666667,0.177777777778,0.176388888889,0.175,0.173611111111,0.172222222222,0.170833333333,0.169444444444,0.168055555556,0.166666666667,0.165277777778,0.163888888889,0.1625,0.161111111111,0.159722222222,0.158333333333,0.156944444444,0.155555555556,0.154166666667,0.152777777778,0.151388888889,0.15,0.148611111111,0.147222222222,0.145833333333,0.144444444444,0.143055555556,0.141666666667,0.140277777778,0.138888888889,0.1375,0.136111111111,0.134722222222,0.133333333333,0.131944444444,0.130555555556,0.129166666667,0.127777777778,0.126388888889,0.125,0.123611111111,0.122222222222,0.120833333333,0.119444444444,0.118055555556,0.116666666667,0.115277777778,0.113888888889,0.1125,0.111111111111,0.109722222222,0.108333333333,0.106944444444,0.105555555556,0.104166666667,0.102777777778,0.101388888889,0.1,0.098611111111,0.097222222222,0.095833333333,0.094444444444,0.093055555556,0.091666666667,0.090277777778,0.088888888889,0.0875,0.086111111111,0.084722222222,0.083333333333,0.081944444444,0.080555555556,0.079166666667,0.077777777778,0.076388888889,0.075,0.073611111111,0.072222222222,0.070833333333,0.069444444444,0.068055555556,0.066666666667,0.065277777778,0.063888888889,0.0625,0.061111111111,0.059722222222,0.058333333333,0.056944444444,0.055555555556,0.054166666667,0.052777777778,0.051388888889,0.05,0.048611111111,0.047222222222,0.045833333333,0.044444444444,0.043055555556,0.041666666667,0.040277777778,0.038888888889,0.0375,0.036111111111,0.034722222222,0.033333333333,0.031944444444,0.030555555556,0.029166666667,0.027777777778,0.026388888889,0.025,0.023611111111,0.022222222222,0.020833333333,0.019444444444,0.018055555556,0.016666666667,0.015277777778,0.013888888889,0.0125,0.011111111111,0.009722222222,0.008333333333,0.006944444444,0.005555555556,0.004166666667,0.002777777778,0.001388888889,]
#external45_data = [-0.001373625452,-0.002717377028,-0.00403218806,-0.005318934508,-0.006578439732,-0.007811478754,-0.009018782081,-0.010201039151,-0.011358901433,-0.01249298523,-0.013603874226,-0.014692121785,-0.015758253053,-0.016802766868,-0.017826137508,-0.018828816289,-0.019811233024,-0.020773797371,-0.021716900067,-0.022640914066,-0.023546195583,-0.02443308507,-0.025301908106,-0.026152976227,-0.026986587696,-0.027803028216,-0.028602571593,-0.029385480351,-0.030152006309,-0.030902391115,-0.031636866748,-0.032355655981,-0.03305897282,-0.033747022914,-0.034420003934,-0.035078105936,-0.035721511693,-0.036350397016,-0.036964931046,-0.037565276538,-0.038151590118,-0.038724022536,-0.039282718898,-0.039827818879,-0.040359456941,-0.04087776252,-0.041382860213,-0.041874869954,-0.042353907175,-0.042820082967,-0.043273504219,-0.043714273767,-0.044142490518,-0.044558249578,-0.044961642368,-0.045352756738,-0.045731677071,-0.046098484383,-0.046453256416,-0.046796067734,-0.047126989799,-0.047446091057,-0.047753437014,-0.048049090302,-0.048333110755,-0.048605555467,-0.048866478854,-0.049115932713,-0.049353966274,-0.04958062625,-0.049795956885,-0.05,-0.050192795035,-0.050374379085,-0.050544786941,-0.050704051121,-0.050852201901,-0.05098926735,-0.051115273347,-0.051230243617,-0.051334199746,-0.051427161202,-0.051509145358,-0.051580167503,-0.051640240861,-0.051689376598,-0.051727583837,-0.051754869666,-0.051771239142,-0.051776695297,-0.051771239142,-0.051754869666,-0.051727583837,-0.051689376598,-0.051640240861,-0.051580167503,-0.051509145358,-0.051427161202,-0.051334199746,-0.051230243617,-0.051115273347,-0.05098926735,-0.050852201901,-0.050704051121,-0.050544786941,-0.050374379085,-0.050192795035,-0.05,-0.049795956885,-0.04958062625,-0.049353966274,-0.049115932713,-0.048866478854,-0.048605555467,-0.048333110755,-0.048049090302,-0.047753437014,-0.047446091057,-0.047126989799,-0.046796067734,-0.046453256416,-0.046098484383,-0.045731677071,-0.045352756738,-0.044961642368,-0.044558249578,-0.044142490518,-0.043714273767,-0.043273504219,-0.042820082967,-0.042353907175,-0.041874869954,-0.041382860213,-0.04087776252,-0.040359456941,-0.039827818879,-0.039282718898,-0.038724022536,-0.038151590118,-0.037565276538,-0.036964931046,-0.036350397016,-0.035721511693,-0.035078105936,-0.034420003934,-0.033747022914,-0.03305897282,-0.032355655981,-0.031636866748,-0.030902391115,-0.030152006309,-0.029385480351,-0.028602571593,-0.027803028216,-0.026986587696,-0.026152976227,-0.025301908106,-0.02443308507,-0.023546195583,-0.022640914066,-0.021716900067,-0.020773797371,-0.019811233024,-0.018828816289,-0.017826137508,-0.016802766868,-0.015758253053,-0.014692121785,-0.013603874226,-0.01249298523,-0.011358901433,-0.010201039151,-0.009018782081,-0.007811478754,-0.006578439732,-0.005318934508,-0.00403218806,-0.002717377028,-0.001373625452,-0.0,0.001388888889,0.002777777778,0.004166666667,0.005555555556,0.006944444445,0.008333333334,0.009722222223,0.011111111112,0.0125,0.013888888889,0.015277777778,0.016666666667,0.018055555556,0.019444444445,0.020833333334,0.022222222223,0.023611111112,0.025,0.026388888889,0.027777777778,0.029166666667,0.030555555556,0.031944444445,0.033333333334,0.034722222223,0.036111111111,0.0375,0.038888888889,0.040277777778,0.041666666667,0.043055555556,0.044444444445,0.045833333334,0.047222222223,0.048611111111,0.05,0.051388888889,0.052777777778,0.054166666667,0.055555555556,0.056944444445,0.058333333334,0.059722222223,0.061111111111,0.0625,0.063888888889,0.065277777778,0.066666666667,0.068055555556,0.069444444445,0.070833333334,0.072222222223,0.073611111111,0.075,0.076388888889,0.077777777778,0.079166666667,0.080555555556,0.081944444445,0.083333333334,0.084722222223,0.086111111111,0.0875,0.088888888889,0.090277777778,0.091666666667,0.093055555556,0.094444444445,0.095833333334,0.097222222223,0.098611111111,0.1,0.101388888889,0.102777777778,0.104166666667,0.105555555556,0.106944444445,0.108333333334,0.109722222222,0.111111111111,0.1125,0.113888888889,0.115277777778,0.116666666667,0.118055555556,0.119444444445,0.120833333334,0.122222222222,0.123611111111,0.125,0.126388888889,0.127777777778,0.129166666667,0.130555555556,0.131944444445,0.133333333334,0.134722222222,0.136111111111,0.1375,0.138888888889,0.140277777778,0.141666666667,0.143055555556,0.144444444445,0.145833333334,0.147222222222,0.148611111111,0.15,0.151388888889,0.152777777778,0.154166666667,0.155555555556,0.156944444445,0.158333333334,0.159722222222,0.161111111111,0.1625,0.163888888889,0.165277777778,0.166666666667,0.168055555556,0.169444444445,0.170833333334,0.172222222222,0.173611111111,0.175,0.176388888889,0.177777777778,0.179166666667,0.180555555556,0.181944444445,0.183333333334,0.184722222222,0.186111111111,0.1875,0.188888888889,0.190277777778,0.191666666667,0.193055555556,0.194444444445,0.195833333333,0.197222222222,0.198611111111,0.2,0.201388888889,0.202777777778,0.204166666667,0.205555555556,0.206944444445,0.208333333333,0.209722222222,0.211111111111,0.2125,0.213888888889,0.215277777778,0.216666666667,0.218055555556,0.219444444445,0.220833333333,0.222222222222,0.223611111111,0.225,0.226388888889,0.227777777778,0.229166666667,0.230555555556,0.231944444445,0.233333333333,0.234722222222,0.236111111111,0.2375,0.238888888889,0.240277777778,0.241666666667,0.243055555556,0.244444444445,0.245833333333,0.247222222222,0.248611111111,0.25,0.251388888889,0.252777777778,0.254166666667,0.255555555556,0.256944444445,0.258333333333,0.259722222222,0.261111111111,0.2625,0.263888888889,0.265277777778,0.266666666667,0.268055555556,0.269444444445,0.270833333333,0.272222222222,0.273611111111,0.275,0.276388888889,0.277777777778,0.279166666667,0.280555555556,0.281944444444,0.283333333333,0.284722222222,0.286111111111,0.2875,0.288888888889,0.290277777778,0.291666666667,0.293055555556,0.294444444444,0.295833333333,0.297222222222,0.298611111111,0.3,0.301388888889,0.302777777778,0.304166666667,0.305555555556,0.306944444444,0.308333333333,0.309722222222,0.311111111111,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.3125,0.311111111111,0.309722222222,0.308333333333,0.306944444444,0.305555555556,0.304166666667,0.302777777778,0.301388888889,0.3,0.298611111111,0.297222222222,0.295833333333,0.294444444444,0.293055555556,0.291666666667,0.290277777778,0.288888888889,0.2875,0.286111111111,0.284722222222,0.283333333333,0.281944444444,0.280555555556,0.279166666667,0.277777777778,0.276388888889,0.275,0.273611111111,0.272222222222,0.270833333333,0.269444444444,0.268055555556,0.266666666667,0.265277777778,0.263888888889,0.2625,0.261111111111,0.259722222222,0.258333333333,0.256944444444,0.255555555556,0.254166666667,0.252777777778,0.251388888889,0.25,0.248611111111,0.247222222222,0.245833333333,0.244444444444,0.243055555555,0.241666666667,0.240277777778,0.238888888889,0.2375,0.236111111111,0.234722222222,0.233333333333,0.231944444444,0.230555555555,0.229166666667,0.227777777778,0.226388888889,0.225,0.223611111111,0.222222222222,0.220833333333,0.219444444444,0.218055555555,0.216666666667,0.215277777778,0.213888888889,0.2125,0.211111111111,0.209722222222,0.208333333333,0.206944444444,0.205555555555,0.204166666667,0.202777777778,0.201388888889,0.2,0.198611111111,0.197222222222,0.195833333333,0.194444444444,0.193055555555,0.191666666667,0.190277777778,0.188888888889,0.1875,0.186111111111,0.184722222222,0.183333333333,0.181944444444,0.180555555555,0.179166666667,0.177777777778,0.176388888889,0.175,0.173611111111,0.172222222222,0.170833333333,0.169444444444,0.168055555555,0.166666666667,0.165277777778,0.163888888889,0.1625,0.161111111111,0.159722222222,0.158333333333,0.156944444444,0.155555555555,0.154166666667,0.152777777778,0.151388888889,0.15,0.148611111111,0.147222222222,0.145833333333,0.144444444444,0.143055555555,0.141666666667,0.140277777778,0.138888888889,0.1375,0.136111111111,0.134722222222,0.133333333333,0.131944444444,0.130555555555,0.129166666667,0.127777777778,0.126388888889,0.125,0.123611111111,0.122222222222,0.120833333333,0.119444444444,0.118055555555,0.116666666667,0.115277777778,0.113888888889,0.1125,0.111111111111,0.109722222222,0.108333333333,0.106944444444,0.105555555555,0.104166666666,0.102777777778,0.101388888889,0.1,0.098611111111,0.097222222222,0.095833333333,0.094444444444,0.093055555555,0.091666666666,0.090277777778,0.088888888889,0.0875,0.086111111111,0.084722222222,0.083333333333,0.081944444444,0.080555555555,0.079166666666,0.077777777778,0.076388888889,0.075,0.073611111111,0.072222222222,0.070833333333,0.069444444444,0.068055555555,0.066666666666,0.065277777778,0.063888888889,0.0625,0.061111111111,0.059722222222,0.058333333333,0.056944444444,0.055555555555,0.054166666666,0.052777777778,0.051388888889,0.05,0.048611111111,0.047222222222,0.045833333333,0.044444444444,0.043055555555,0.041666666666,0.040277777778,0.038888888889,0.0375,0.036111111111,0.034722222222,0.033333333333,0.031944444444,0.030555555555,0.029166666666,0.027777777778,0.026388888889,0.025,0.023611111111,0.022222222222,0.020833333333,0.019444444444,0.018055555555,0.016666666666,0.015277777778,0.013888888889,0.0125,0.011111111111,0.009722222222,0.008333333333,0.006944444444,0.005555555555,0.004166666666,0.002777777778,0.001388888889,]

#multi3_int_data =(-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,0.007216878365,0.01443375673,0.021650635095,0.028867513459,0.036084391824,0.043301270189,0.050518148554,0.057735026919,0.064951905284,0.072168783649,0.079385662014,0.086602540378,0.093819418743,0.101036297108,0.108253175473,0.115470053838,0.122686932203,0.129903810568,0.137120688933,0.144337567297,0.151554445662,0.158771324027,0.165988202392,0.173205080757,0.180421959122,0.187638837487,0.194855715851,0.202072594216,0.209289472581,0.216506350946,0.223723229311,0.230940107676,0.238156986041,0.245373864406,0.25259074277,0.259807621135,0.2670244995,0.274241377865,0.28145825623,0.288675134595,0.29589201296,0.303108891325,0.310325769689,0.317542648054,0.324759526419,0.331976404784,0.339193283149,0.346410161514,0.353627039879,0.360843918243,0.368060796608,0.375277674973,0.382494553338,0.389711431703,0.396928310068,0.404145188433,0.411362066798,0.418578945162,0.425795823527,0.433012701892,0.440229580257,0.447446458622,0.454663336987,0.461880215352,0.469097093717,0.476313972081,0.483530850446,0.490747728811,0.497964607176,0.505181485541,0.512398363906,0.519615242271,0.526832120636,0.534048999,0.541265877365,0.547673314821,0.5528711653,0.557223135528,0.560927686209,0.56410705064,0.56684252132,0.56919103344,0.571193900198,0.57288180558,0.57427783534,0.575399400317,0.576259494329,0.576867529433,0.577229887482,0.57735026919,0.577229887482,0.576867529433,0.576259494329,0.575399400317,0.57427783534,0.57288180558,0.571193900198,0.56919103344,0.56684252132,0.56410705064,0.560927686209,0.557223135528,0.5528711653,0.547673314821,0.541265877365,0.534048999001,0.526832120636,0.519615242271,0.512398363906,0.505181485541,0.497964607176,0.490747728811,0.483530850447,0.476313972082,0.469097093717,0.461880215352,0.454663336987,0.447446458622,0.440229580257,0.433012701892,0.425795823528,0.418578945163,0.411362066798,0.404145188433,0.396928310068,0.389711431703,0.382494553338,0.375277674973,0.368060796609,0.360843918244,0.353627039879,0.346410161514,0.339193283149,0.331976404784,0.324759526419,0.317542648055,0.31032576969,0.303108891325,0.29589201296,0.288675134595,0.28145825623,0.274241377865,0.2670244995,0.259807621136,0.252590742771,0.245373864406,0.238156986041,0.230940107676,0.223723229311,0.216506350946,0.209289472581,0.202072594217,0.194855715852,0.187638837487,0.180421959122,0.173205080757,0.165988202392,0.158771324027,0.151554445663,0.144337567298,0.137120688933,0.129903810568,0.122686932203,0.115470053838,0.108253175473,0.101036297108,0.093819418744,0.086602540379,0.079385662014,0.072168783649,0.064951905284,0.057735026919,0.050518148554,0.043301270189,0.036084391825,0.02886751346,0.021650635095,0.01443375673,0.007216878365,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,0.0,)
#multi3_ext_data =(-0.006778280188,-0.012814874909,-0.018258443075,-0.023210575868,-0.027744373085,-0.031914516323,-0.035763165074,-0.039323617685,-0.042622693966,-0.045682346547,-0.048520785999,-0.051153287908,-0.05359278529,-0.055850312148,-0.057935341316,-0.059856045664,-0.061619502667,-0.063231856427,-0.06469844723,-0.066023915948,-0.067212288714,-0.068267045903,-0.069191178464,-0.069987233927,-0.070657353858,-0.071203304134,-0.071626499073,-0.071928020232,-0.07210863046,-0.072168783647,-0.07210863046,-0.071928020232,-0.071626499073,-0.071203304134,-0.070657353858,-0.069987233927,-0.069191178464,-0.068267045903,-0.067212288714,-0.066023915948,-0.06469844723,-0.063231856427,-0.061619502667,-0.059856045664,-0.057935341316,-0.055850312148,-0.05359278529,-0.051153287908,-0.048520785999,-0.045682346547,-0.042622693966,-0.039323617685,-0.035763165074,-0.031914516323,-0.027744373085,-0.023210575868,-0.018258443075,-0.012814874909,-0.006778280188,-1e-12,0.007216878368,0.014433756733,0.021650635097,0.028867513462,0.036084391827,0.043301270192,0.050518148557,0.057735026922,0.064951905286,0.072168783651,0.079385662016,0.086602540381,0.093819418746,0.101036297111,0.108253175475,0.11547005384,0.122686932205,0.12990381057,0.137120688935,0.1443375673,0.151554445664,0.158771324029,0.165988202394,0.173205080759,0.180421959124,0.187638837489,0.194855715853,0.202072594218,0.209289472583,0.216506350948,0.223723229313,0.230940107678,0.238156986042,0.245373864407,0.252590742772,0.259807621137,0.267024499502,0.274241377867,0.281458256231,0.288675134596,0.295892012961,0.303108891326,0.310325769691,0.317542648056,0.32475952642,0.331976404785,0.33919328315,0.346410161515,0.35362703988,0.360843918245,0.368060796609,0.375277674974,0.382494553339,0.389711431704,0.396928310069,0.404145188433,0.411362066798,0.418578945163,0.425795823528,0.433012701893,0.440229580258,0.447446458622,0.454663336987,0.461880215352,0.469097093717,0.476313972082,0.483530850447,0.490747728811,0.497964607176,0.505181485541,0.512398363906,0.519615242271,0.526832120636,0.534048999,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.541265877365,0.534048999,0.526832120636,0.519615242271,0.512398363906,0.505181485541,0.497964607176,0.490747728811,0.483530850446,0.476313972081,0.469097093717,0.461880215352,0.454663336987,0.447446458622,0.440229580257,0.433012701892,0.425795823527,0.418578945162,0.411362066798,0.404145188433,0.396928310068,0.389711431703,0.382494553338,0.375277674973,0.368060796608,0.360843918244,0.353627039879,0.346410161514,0.339193283149,0.331976404784,0.324759526419,0.317542648054,0.310325769689,0.303108891325,0.29589201296,0.288675134595,0.28145825623,0.274241377865,0.2670244995,0.259807621135,0.25259074277,0.245373864406,0.238156986041,0.230940107676,0.223723229311,0.216506350946,0.209289472581,0.202072594216,0.194855715851,0.187638837487,0.180421959122,0.173205080757,0.165988202392,0.158771324027,0.151554445662,0.144337567297,0.137120688933,0.129903810568,0.122686932203,0.115470053838,0.108253175473,0.101036297108,0.093819418743,0.086602540378,0.079385662014,0.072168783649,0.064951905284,0.057735026919,0.050518148554,0.043301270189,0.036084391824,0.028867513459,0.021650635095,0.01443375673,0.007216878365,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,)

#internal2S_data = [-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,-0.0,0.004811279452,0.009622558905,0.014433838357,0.019245117809,0.024056397261,0.028867676714,0.033678956166,0.038490235618,0.043301515071,0.048112794523,0.052924073975,0.057735353427,0.06254663288,0.067357912332,0.072169191784,0.076980471237,0.081791750689,0.086603030141,0.091414309593,0.096225589046,0.101036868498,0.10584814795,0.110659427403,0.115470706855,0.120281986307,0.12509326576,0.129904545212,0.134715824664,0.139527104116,0.144338383569,0.149149663021,0.153960942473,0.158772221926,0.163583501378,0.16839478083,0.173206060282,0.178017339735,0.182828619187,0.187639898639,0.192451178092,0.197262457544,0.202073736996,0.206885016448,0.211696295901,0.216507575353,0.221318854805,0.226130134258,0.23094141371,0.235752693162,0.240563972614,0.245375252067,0.250186531519,0.254997810971,0.259809090424,0.264620369876,0.269431649328,0.27424292878,0.279054208233,0.283865487685,0.288676767137,0.29348804659,0.298299326042,0.303110605494,0.307921884946,0.312733164399,0.317544443851,0.322355723303,0.327167002756,0.331978282208,0.33678956166,0.341600841113,0.346412120565,0.351223400017,0.356034679469,0.360845958922,0.365657238374,0.370468517826,0.375279797279,0.380091076731,0.384902356183,0.389713635635,0.394524915088,0.39933619454,0.404147473992,0.408958753445,0.413770032897,0.418581312349,0.423392591801,0.428203871254,0.433015150706,0.437826430158,0.442637709611,0.447448989063,0.452260268515,0.457071547967,0.46188282742,0.466694106872,0.471505386324,0.476316665777,0.481127945229,0.485939224681,0.490750504133,0.495561783586,0.500373063038,0.50518434249,0.509995621943,0.514806901395,0.519618180847,0.524429460299,0.529240739752,0.534052019204,0.538863298656,0.543574230063,0.547676454226,0.551248893689,0.554407036112,0.557226361347,0.559759404764,0.562044440121,0.564110326611,0.56597940937,0.567669351749,0.569194344037,0.570565929497,0.571793585533,0.572885142526,0.573847091694,0.574684814962,0.575402758649,0.576004565696,0.576493176578,0.576870905964,0.577139500113,0.577300178463,0.577353661816,0.577300188674,0.577139520581,0.57687093678,0.576493217883,0.576004617684,0.575402821569,0.574684889128,0.573847177489,0.572885240417,0.571793696083,0.570566053385,0.569194482084,0.56766950495,0.565979578942,0.564110514058,0.562044647329,0.55975963414,0.557226616038,0.55440732035,0.5512492134,0.547676818145,0.543574652051,0.53886379862,0.534052600794,0.529241402969,0.524430205143,0.519619007317,0.514807809491,0.509996611665,0.505185413839,0.500374216013,0.495563018188,0.490751820362,0.485940622536,0.48112942471,0.476318226884,0.471507029058,0.466695831232,0.461884633407,0.457073435581,0.452262237755,0.447451039929,0.442639842103,0.437828644277,0.433017446451,0.428206248626,0.4233950508,0.418583852974,0.413772655148,0.408961457322,0.404150259496,0.39933906167,0.394527863845,0.389716666019,0.384905468193,0.380094270367,0.375283072541,0.370471874715,0.365660676889,0.360849479064,0.356038281238,0.351227083412,0.346415885586,0.34160468776,0.336793489934,0.331982292108,0.327171094283,0.322359896457,0.317548698631,0.312737500805,0.307926302979,0.303115105153,0.298303907327,0.293492709502,0.288681511676,0.28387031385,0.279059116024,0.274247918198,0.269436720372,0.264625522546,0.259814324721,0.255003126895,0.250191929069,0.245380731243,0.240569533417,0.235758335591,0.230947137765,0.22613593994,0.221324742114,0.216513544288,0.211702346462,0.206891148636,0.20207995081,0.197268752985,0.192457555159,0.187646357333,0.182835159507,0.178023961681,0.173212763855,0.168401566029,0.163590368204,0.158779170378,0.153967972552,0.149156774726,0.1443455769,0.139534379074,0.134723181248,0.129911983423,0.125100785597,0.120289587771,0.115478389945,0.110667192119,0.105855994293,0.101044796467,0.096233598642,0.091422400816,0.08661120299,0.081800005164,0.076988807338,0.072177609512,0.067366411686,0.062555213861,0.057744016035,0.052932818209,0.048121620383,0.043310422557,0.038499224731,0.033688026905,0.02887682908,0.024065631254,0.019254433428,0.014443235602,0.009632037776,0.00482083995,9.642124e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,2.754918e-06,]
#external2S_data = [-0.004610509437,-0.008864261505,-0.01281484414,-0.016502787814,-0.019959638539,-0.023210526211,-0.026275857144,-0.029172470647,-0.031914453753,-0.034513730164,-0.036980495571,-0.039323545713,-0.041550527849,-0.043668136434,-0.045682267448,-0.04759814157,-0.049420403565,-0.051153203265,-0.052800262124,-0.054364928386,-0.055850223123,-0.057258878931,-0.058593372644,-0.059855953149,-0.06104866515,-0.06217336957,-0.063231761131,-0.064225383563,-0.0651556428,-0.066023818454,-0.066831073828,-0.067578464649,-0.068266946707,-0.068897382525,-0.069470547196,-0.069987133462,-0.070447756139,-0.070852955945,-0.07120320279,-0.071498898583,-0.071740379589,-0.071927918371,-0.072061725347,-0.072141949981,-0.072168681616,-0.072141949981,-0.072061725347,-0.071927918371,-0.071740379589,-0.071498898583,-0.07120320279,-0.070852955945,-0.070447756139,-0.069987133462,-0.069470547196,-0.068897382525,-0.068266946707,-0.067578464649,-0.066831073828,-0.066023818454,-0.0651556428,-0.064225383563,-0.06323176113,-0.062173369569,-0.06104866515,-0.059855953149,-0.058593372644,-0.057258878931,-0.055850223122,-0.054364928385,-0.052800262123,-0.051153203264,-0.049420403565,-0.047598141569,-0.045682267447,-0.043668136433,-0.041550527848,-0.039323545712,-0.03698049557,-0.034513730163,-0.031914453752,-0.029172470646,-0.026275857143,-0.02321052621,-0.019959638538,-0.016502787813,-0.012814844138,-0.008864261504,-0.004610509435,-0.0,0.004811279455,0.009622558907,0.01443383836,0.019245117812,0.024056397264,0.028867676716,0.033678956169,0.038490235621,0.043301515073,0.048112794525,0.052924073978,0.05773535343,0.062546632882,0.067357912334,0.072169191787,0.076980471239,0.081791750691,0.086603030143,0.091414309596,0.096225589048,0.1010368685,0.105848147952,0.110659427405,0.115470706857,0.120281986309,0.125093265761,0.129904545214,0.134715824666,0.139527104118,0.14433838357,0.149149663023,0.153960942475,0.158772221927,0.163583501379,0.168394780832,0.173206060284,0.178017339736,0.182828619188,0.187639898641,0.192451178093,0.197262457545,0.202073736997,0.20688501645,0.211696295902,0.216507575354,0.221318854806,0.226130134259,0.230941413711,0.235752693163,0.240563972615,0.245375252068,0.25018653152,0.254997810972,0.259809090424,0.264620369877,0.269431649329,0.274242928781,0.279054208233,0.283865487686,0.288676767138,0.29348804659,0.298299326042,0.303110605495,0.307921884947,0.312733164399,0.317544443851,0.322355723304,0.327167002756,0.331978282208,0.33678956166,0.341600841113,0.346412120565,0.351223400017,0.356034679469,0.360845958922,0.365657238374,0.370468517826,0.375279797278,0.380091076731,0.384902356183,0.389713635635,0.394524915087,0.39933619454,0.404147473992,0.408958753444,0.413770032896,0.418581312349,0.423392591801,0.428203871253,0.433015150705,0.437826430158,0.44263770961,0.447448989062,0.452260268514,0.457071547967,0.461882827419,0.466694106871,0.471505386323,0.476316665776,0.481127945228,0.48593922468,0.490750504132,0.495561783585,0.500373063037,0.505184342489,0.509995621941,0.514806901394,0.519618180846,0.524429460298,0.52924073975,0.534052019203,0.538863298655,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.541268938381,0.538863339468,0.534052141642,0.529240943817,0.524429745991,0.519618548165,0.514807350339,0.509996152514,0.505184954688,0.500373756862,0.495562559037,0.490751361211,0.485940163385,0.481128965559,0.476317767734,0.471506569908,0.466695372082,0.461884174257,0.457072976431,0.452261778605,0.447450580779,0.442639382954,0.437828185128,0.433016987302,0.428205789477,0.423394591651,0.418583393825,0.413772195999,0.408960998174,0.404149800348,0.399338602522,0.394527404696,0.389716206871,0.384905009045,0.380093811219,0.375282613394,0.370471415568,0.365660217742,0.360849019916,0.356037822091,0.351226624265,0.346415426439,0.341604228614,0.336793030788,0.331981832962,0.327170635136,0.322359437311,0.317548239485,0.312737041659,0.307925843833,0.303114646008,0.298303448182,0.293492250356,0.288681052531,0.283869854705,0.279058656879,0.274247459053,0.269436261228,0.264625063402,0.259813865576,0.255002667751,0.250191469925,0.245380272099,0.240569074273,0.235757876448,0.230946678622,0.226135480796,0.22132428297,0.216513085145,0.211701887319,0.206890689493,0.202079491668,0.197268293842,0.192457096016,0.18764589819,0.182834700365,0.178023502539,0.173212304713,0.168401106888,0.163589909062,0.158778711236,0.15396751341,0.149156315585,0.144345117759,0.139533919933,0.134722722108,0.129911524282,0.125100326456,0.12028912863,0.115477930805,0.110666732979,0.105855535153,0.101044337327,0.096233139502,0.091421941676,0.08661074385,0.081799546025,0.076988348199,0.072177150373,0.067365952547,0.062554754722,0.057743556896,0.05293235907,0.048121161245,0.043309963419,0.038498765593,0.033687567767,0.028876369942,0.024065172116,0.01925397429,0.014442776464,0.009631578639,0.004820380813,9.182987e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,2.295753e-06,]
